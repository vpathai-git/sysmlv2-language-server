standard library package TestPackage {
    private import Base::Anything;
    private import Occurrences::occurrences;
    private import SequenceFunctions::union;

    class TestClass specializes Anything {
    }
}
